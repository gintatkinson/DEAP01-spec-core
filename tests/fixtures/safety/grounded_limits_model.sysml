package GroundedLimits_SSOT {
    doc /* Ground truth limits for flight envelope verification */
    attribute catapultPressureLimitBar : Real = 15.0;
    attribute climbAltitudeLimitM : Real = 60.0;
    attribute loiterRadiusLimitM : Real = 350.0;
    attribute terminalDiveSpeedLimitMps : Real = 60.0;
    attribute clearAltitudeLimitM : Real = 60.0;
}
